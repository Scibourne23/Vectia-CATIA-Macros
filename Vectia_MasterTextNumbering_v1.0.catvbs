' CATScript: Vectia_MasterTextNumbering_v1.0
'
' Purpose: The flagship macro for creating visually perfect, associative VVNN numbering.
'          It uses a pre-selected text object as a template for style and custom framing.
'
' This is the official numbering tool for the Vectia suite.
'
' Features:
'   - Master Text Workflow: Uses ANY pre-selected, custom-formatted text as a template.
'   - Auto-Deletion: Asks to delete the master text object upon successful completion.
'   - Multi-View Processing: Automatically handles items selected across multiple drawing views.
'   - User-Defined Start: Prompts the user for a starting view number (VV).
'   - SMART GDTs: Automatically applies multipliers to GDTs that have NO leaders.
'   - Scale Independence: Automatically adjusts text placement offsets based on the scale of the target view.
'   - Format Options: Allows the user to choose between long (0101,..,0104) and short (0101,..,04) numbering.

Option Explicit

' --- Global Constants ---
' To adjust text placement, edit these values. Offsets are relative to a 1:1 scale view.
Const DIM_TEXT_VERTICAL_OFFSET = 13
Const GDT_TEXT_VERTICAL_OFFSET = -10

' =================================================================================================
' Main Subroutine
' =================================================================================================
Sub CATMain()

    ' --- Instruction Box ---
    Dim instructionMsg
    instructionMsg = "--- Vectia Master Text Numbering v1.0 ---" & vbCrLf & vbCrLf & _
                   "WORKFLOW:" & vbCrLf & _
                   "1. Create or identify a 'Master Text' with your custom frame." & vbCrLf & _
                   "2. Select the Master DrawingText object FIRST." & vbCrLf & _
                   "3. Hold CTRL and select all target Dimensions and GDTs." & vbCrLf & vbCrLf & _
                   "Click OK to continue..."
    MsgBox instructionMsg, vbInformation, "Macro Instructions"

    ' --- User prompt to select the numbering format ---
    Dim useShortFormat, userChoice
    userChoice = MsgBox("Use 'Short Format' for multi-instance notes?" & vbCrLf & vbCrLf & _
                        "  Yes = 0101,..,04" & vbCrLf & _
                        "  No  = 0101,..,0104", vbYesNo + vbQuestion, "Select Numbering Format")
    If userChoice = vbYes Then
        useShortFormat = True
    Else
        useShortFormat = False
    End If

    ' --- Variable Declarations ---
    Dim oCATIA, oDrwDocument, oActiveSheet, oAllViews, oSelection
    Dim oMasterText, masterItemType
    Dim viewDataMap, targetList, userInput, userStartVV
    Dim i_sel, targetItem, parentView, parentViewName
    Dim processedViewCounter, currentVV, sViewIndexPadded
    Dim viewData, summaryLog, totalItemsNumbered, totalErrors
    
    ' --- Context-Aware Memory Variables ---
    Dim lastItemWasMultiInstance, lastNValue, lastDimInfo
    lastItemWasMultiInstance = False: lastNValue = 1: lastDimInfo = ""

    ' --- Basic CATIA Application Setup ---
    Set oCATIA = CATIA
    Set oDrwDocument = oCATIA.ActiveDocument
    If TypeName(oDrwDocument) <> "DrawingDocument" Then MsgBox "Active doc must be a Drawing.", vbCritical: Exit Sub
    Set oActiveSheet = oDrwDocument.Sheets.ActiveSheet
    Set oAllViews = oActiveSheet.Views
    
    ' --- Get User Selection & Validate Master Text ---
    Set oSelection = oDrwDocument.Selection
    If oSelection.Count < 2 Then MsgBox "Error: Select Master Text, then at least one target.", vbCritical: Exit Sub
    Set oMasterText = oSelection.Item(1).Value
    If TypeName(oMasterText) <> "DrawingText" Then MsgBox "Error: The FIRST selected item must be the Master Text object.", vbCritical: Exit Sub
    
    ' --- Get User Input for Starting VV ---
    userInput = InputBox("Please enter the starting view number (VV).", "Enter Starting VV", "1")
    If Not IsNumeric(userInput) Or userInput = "" Then MsgBox "Invalid input or cancelled.", vbInformation: Exit Sub
    userStartVV = CLng(userInput)

    ' --- Pre-Scan to build BOTH the view map AND a stable list of targets ---
    Set viewDataMap = CreateObject("Scripting.Dictionary")
    Set targetList = CreateObject("Scripting.Dictionary")
    processedViewCounter = 0
    For i_sel = 2 To oSelection.Count
        Set targetItem = oSelection.Item(i_sel).Value
        If TypeName(targetItem) = "DrawingDimension" Or TypeName(targetItem) = "DrawingGDT" Then
            targetList.Add i_sel, targetItem
            Set parentView = FindParentViewOf(targetItem, oAllViews)
            If Not parentView Is Nothing Then
                parentViewName = parentView.Name
                If Not viewDataMap.Exists(parentViewName) Then
                    processedViewCounter = processedViewCounter + 1
                    currentVV = userStartVV + processedViewCounter - 1
                    sViewIndexPadded = Right("0" & CStr(currentVV), 2)
                    Set viewData = CreateObject("Scripting.Dictionary")
                    viewData.Add "VV_Prefix", sViewIndexPadded
                    viewData.Add "NextNN", 1
                    viewDataMap.Add parentViewName, viewData
                End If
            End If
        End If
    Next
    If targetList.Count = 0 Then MsgBox "No valid Dimensions or GDTs found in the target selection.", vbInformation : Exit Sub
    MsgBox "Master Text confirmed. Found " & targetList.Count & " targets across " & viewDataMap.Count & " unique view(s).", vbInformation

    ' --- Main Processing Loop ---
    totalItemsNumbered = 0
    totalErrors = 0
    oSelection.Clear: oSelection.Add oMasterText: oSelection.Copy
    For Each i_sel In targetList.Keys
        Set targetItem = targetList.Item(i_sel)
        Set parentView = FindParentViewOf(targetItem, oAllViews)
        If Not parentView Is Nothing Then
            parentViewName = parentView.Name
            If viewDataMap.Exists(parentViewName) Then
                Set viewData = viewDataMap.Item(parentViewName)
                Dim vv_prefix, currentSequenceNN, N_for_this_item
                vv_prefix = viewData("VV_Prefix")
                currentSequenceNN = viewData("NextNN")
                ProcessOneItem targetItem, parentView, vv_prefix, currentSequenceNN, N_for_this_item, totalErrors, lastItemWasMultiInstance, lastNValue, lastDimInfo, useShortFormat
                If N_for_this_item > 0 Then
                    totalItemsNumbered = totalItemsNumbered + 1
                    viewData("NextNN") = currentSequenceNN + N_for_this_item
                End If
            End If
        End If
    Next

    ' --- Final Report ---
    summaryLog = "--- Numbering Finished ---" & vbCrLf & vbCrLf
    summaryLog = summaryLog & "Items Processed: " & totalItemsNumbered & vbCrLf
    summaryLog = summaryLog & "Errors/Warnings: " & totalErrors
    MsgBox summaryLog, vbInformation, "Macro Finished"

    ' --- Ask to delete master text at the very end ---
    Dim confirmDelete
    confirmDelete = MsgBox("Do you want to delete the original Master Text object?", vbYesNo + vbQuestion, "Delete Master?")
    If confirmDelete = vbYes Then
        oSelection.Clear
        oSelection.Add oMasterText
        oSelection.Delete
    End If
    
    oSelection.Clear: Set oCATIA = Nothing
End Sub

' =================================================================================================
' Helper Sub: ProcessOneItem
' =================================================================================================
Private Sub ProcessOneItem(ByVal iTargetItem, ByVal iParentView, ByVal iViewPrefix, ByVal iStartNN, ByRef oN_Value, ByRef ioErrorCount, ByRef ioLastWasMulti, ByRef ioLastN, ByRef ioLastDimInfo, ByVal iUseShortFormat)
    oN_Value = 0
    Dim itemType, placeX, placeY, bGotCoords, N
    itemType = TypeName(iTargetItem)
    placeX = 0.0: placeY = 0.0: bGotCoords = False: N = 1

    If itemType = "DrawingDimension" Then
        ioLastWasMulti = False: ioLastN = 1: ioLastDimInfo = ""
        Dim bboxCoords(7), bCallSucceeded
        bCallSucceeded = False: On Error Resume Next
        iTargetItem.GetBoundaryBox bboxCoords
        If Err.Number = 0 Then bCallSucceeded = True Else ioErrorCount=ioErrorCount+1: Err.Clear
        On Error GoTo 0
        If bCallSucceeded Then
             Dim tX, tY: On Error Resume Next
             tX=bboxCoords(0): tY=bboxCoords(1)
             If Err.Number=0 Then placeX=CDbl(tX): placeY=CDbl(tY): bGotCoords=True Else ioErrorCount=ioErrorCount+1: Err.Clear
             On Error GoTo 0
        End If
        Dim oDimValueObject: On Error Resume Next
        Set oDimValueObject = iTargetItem.GetValue()
        If Not oDimValueObject Is Nothing Then
             Dim cBT, tempN, xPos, numPart
             oDimValueObject.GetBaultText 1, cBT, "", "", ""
             If Len(Trim(cBT)) > 0 Then
                  xPos = InStr(UCase(Trim(cBT)), "X"): If xPos > 1 Then numPart = Trim(Left(Trim(cBT), xPos - 1))
                  If IsNumeric(numPart) Then tempN = CLng(numPart)
                  If tempN > 1 Then
                     N = tempN: ioLastWasMulti = True: ioLastN = N
                     On Error Resume Next: ioLastDimInfo = "Dim val " & CStr(Round(oDimValueObject.Value, 2)): On Error GoTo 0
                  End If
             End If
        End If: On Error GoTo 0
    ElseIf itemType = "DrawingGDT" Then
        On Error Resume Next
        placeX = iTargetItem.x: placeY = iTargetItem.y
        If Err.Number = 0 Then bGotCoords=True Else ioErrorCount=ioErrorCount+1: Err.Clear
        On Error GoTo 0
        If ioLastWasMulti Then
            If iTargetItem.Leaders.Count = 0 Then
                N = ioLastN
            End If
        End If
        ioLastWasMulti = False
    End If
    If Not bGotCoords Then MsgBox "WARN: Could not get coordinates.", vbExclamation: ioErrorCount=ioErrorCount+1: Exit Sub

    Dim outputTextContent, nStart, nEnd, sVVNN
    nStart=iStartNN: nEnd=iStartNN+N-1: sVVNN=FormatSeqNumber(iViewPrefix,nStart)
    If iUseShortFormat Then
        Select Case N
            Case 1: outputTextContent = sVVNN
            Case 2: outputTextContent = sVVNN & "," & Right("0" & CStr(nEnd), 2)
            Case Else: outputTextContent = sVVNN & ",..," & Right("0" & CStr(nEnd), 2)
        End Select
    Else
        Select Case N
            Case 1: outputTextContent = sVVNN
            Case 2: outputTextContent = sVVNN & "," & FormatSeqNumber(iViewPrefix, nEnd)
            Case Else: outputTextContent = sVVNN & ",..," & FormatSeqNumber(iViewPrefix, nEnd)
        End Select
    End If

    Dim oPastedText, textFinalX, textFinalY, oSel, viewScale, dynamicDimOffset, dynamicGdtOffset
    Set oSel = CATIA.ActiveDocument.Selection
    oSel.Clear: oSel.Add iParentView: oSel.Paste
    If oSel.Count = 0 Then MsgBox "ERROR: Paste failed.", vbCritical: ioErrorCount=ioErrorCount+1: Exit Sub
    Set oPastedText = oSel.Item(1).Value
    If TypeName(oPastedText) <> "DrawingText" Then MsgBox "ERROR: Pasted non-text.", vbCritical: ioErrorCount=ioErrorCount+1: Exit Sub
    
    viewScale = iParentView.Scale2: If viewScale <= 0 Then viewScale = 1
    dynamicDimOffset = DIM_TEXT_VERTICAL_OFFSET / viewScale
    dynamicGdtOffset = GDT_TEXT_VERTICAL_OFFSET / viewScale

    If itemType = "DrawingDimension" Then
        textFinalY = placeY + dynamicDimOffset
    ElseIf itemType = "DrawingGDT" Then
        textFinalY = placeY + dynamicGdtOffset
    End If
    
    textFinalX = placeX
    oPastedText.x = textFinalX: oPastedText.y = textFinalY
    oPastedText.Text = outputTextContent
    
    On Error Resume Next: oPastedText.AssociativeElement = iTargetItem
    If Err.Number <> 0 Then MsgBox "WARN: Assoc. failed.", vbExclamation: ioErrorCount=ioErrorCount+1: Err.Clear
    On Error GoTo 0
    oN_Value = N
End Sub

' =================================================================================================
' Helper Function: FindParentViewOf
' =================================================================================================
Private Function FindParentViewOf(ByVal iSelectedItem, ByVal iAllViews)
    Set FindParentViewOf = Nothing: Dim oView, i, selectedItemName
    On Error Resume Next: selectedItemName = iSelectedItem.Name: If Err.Number <> 0 Then selectedItemName = "": On Error GoTo 0
    For Each oView In iAllViews
        On Error Resume Next
        If TypeName(iSelectedItem) = "DrawingDimension" Then
            If oView.Dimensions.Count > 0 Then
                For i = 1 To oView.Dimensions.Count
                    If oView.Dimensions.Item(i) Is iSelectedItem Then Set FindParentViewOf = oView: Exit Function
                Next
            End If
        ElseIf TypeName(iSelectedItem) = "DrawingGDT" Then
            If oView.GDTs.Count > 0 And Len(selectedItemName) > 0 Then
                For i = 1 To oView.GDTs.Count
                    If oView.GDTs.Item(i).Name = selectedItemName Then Set FindParentViewOf = oView: Exit Function
                Next
            End If
        End If
        On Error GoTo 0
    Next
End Function

' =================================================================================================
' Sub-Helper Function: FormatSeqNumber
' =================================================================================================
Private Function FormatSeqNumber(viewPrefixVV, sequenceNN)
    FormatSeqNumber = viewPrefixVV & Right("0" & CStr(sequenceNN), 2)
End Function
