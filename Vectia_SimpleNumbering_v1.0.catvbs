' CATScript: Vectia_SimpleNumbering_v1.0
'
' Purpose: A foundational macro that creates associative VVNN numbering text for
'          pre-selected Dimensions and GDTs within the ACTIVE VIEW only.
'
' This is the v1.0 base for the Vectia numbering tools.

Option Explicit

Sub CATMain()

    Const TEXT_VERTICAL_OFFSET = 13 ' mm Offset ABOVE the element

    ' --- Variable Declarations (Pure VBScript) ---
    Dim oCATIA, oDrwDocument, oActiveSheet, oActiveView, sActiveViewName
    Dim oViews, viewIndex, activeViewFoundIndex, oView
    Dim processedViewIndex, sViewIndexPadded, currentSequenceNN
    Dim oSelection, i, validationFailed, itemType, selectedItem
    Dim totalItemsProcessed, totalTextsCreated, totalAssocSetSuccess, totalErrorsEncountered
    Dim objToNumber, oTexts, bboxCoords(7)

    ' --- Basic CATIA Application Setup ---
    Set oCATIA = CATIA
    If oCATIA Is Nothing Then MsgBox "CRIT ERR: Get CATIA App Failed.", vbCritical: Exit Sub

    Set oDrwDocument = oCATIA.ActiveDocument
    If oDrwDocument Is Nothing Then MsgBox "ERR: No active document.", vbExclamation: Exit Sub
    If TypeName(oDrwDocument) <> "DrawingDocument" Then MsgBox "ERR: Active doc not Drawing.", vbCritical: Exit Sub

    On Error Resume Next
    Set oActiveSheet = oDrwDocument.Sheets.ActiveSheet
    If Err.Number<>0 Or oActiveSheet Is Nothing Then MsgBox "ERR: Get Active Sheet Failed. Err:"&Err.Description, vbCritical: Err.Clear: On Error GoTo 0: Exit Sub

    Set oActiveView = oActiveSheet.Views.ActiveView
    If Err.Number<>0 Or oActiveView Is Nothing Then MsgBox "ERR: Get Active View Failed. Err:"&Err.Description, vbCritical: Err.Clear: On Error GoTo 0: Exit Sub
    sActiveViewName = oActiveView.Name
    On Error GoTo 0

    ' --- Find Active View Index ---
    Set oViews = oActiveSheet.Views
    activeViewFoundIndex = 0
    For viewIndex = 1 To oViews.Count
        Set oView = oViews.Item(viewIndex)
        If oView Is oActiveView Then
            activeViewFoundIndex = viewIndex
            Exit For
        End If
        Set oView = Nothing
    Next
    If activeViewFoundIndex = 0 Then MsgBox "ERR: Cannot find active view index.", vbCritical: Exit Sub
    If activeViewFoundIndex <= 2 Then MsgBox "WARN: Active view is main/background. Numbering may be unexpected.", vbExclamation

    ' Calculate CORRECT VV Prefix
    processedViewIndex = activeViewFoundIndex - 2
    If processedViewIndex < 1 Then processedViewIndex = 1
    sViewIndexPadded = Right("0" & CStr(processedViewIndex), 2)
    MsgBox "View: '" & sActiveViewName & "' | Prefix(VV):" & sViewIndexPadded, vbInformation

    ' Initialize sequence counter
    currentSequenceNN = 1
    MsgBox "Numbering starts NN = " & currentSequenceNN, vbInformation, "Sequence Start"

    ' --- Get CURRENT Selection ---
    Set oSelection = oDrwDocument.Selection
    If oSelection.Count = 0 Then MsgBox "No Dimensions or GD&Ts selected.", vbExclamation: Exit Sub

    ' --- Validate Selection ---
    validationFailed = False
    For i = 1 To oSelection.Count
        Set selectedItem = oSelection.Item(i).Value
        itemType = TypeName(selectedItem)
        If itemType <> "DrawingDimension" And itemType <> "DrawingGDT" Then
            MsgBox "ERROR: Item #" & i & " not Dim or GDT.", vbCritical
            validationFailed=True: Set selectedItem=Nothing: Exit For
        End If
    Next
    If validationFailed Then Exit Sub

    MsgBox "Processing " & oSelection.Count & " selected items...", vbInformation

    ' --- Initialize Counters ---
    totalItemsProcessed = 0: totalTextsCreated = 0: totalAssocSetSuccess = 0: totalErrorsEncountered = 0
    Set oTexts = oActiveView.Texts
    
    ' --- Main Loop ---
    For i = 1 To oSelection.Count
        Set objToNumber = oSelection.Item(i).Value
        totalItemsProcessed = totalItemsProcessed + 1
        itemType = TypeName(objToNumber)

        Dim placeX, placeY, bGotCoords, N
        placeX = 0.0: placeY = 0.0: bGotCoords = False: N = 1

        ' Get Coordinates & Instance Count
        If itemType = "DrawingDimension" Then
            Dim bCallSucceeded: bCallSucceeded = False
            On Error Resume Next: objToNumber.GetBoundaryBox bboxCoords
            If Err.Number=0 Then bCallSucceeded = True Else totalErrorsEncountered=totalErrorsEncountered+1: Err.Clear
            On Error GoTo 0
            If bCallSucceeded Then
                 Dim tX, tY: On Error Resume Next
                 tX=bboxCoords(0): tY=bboxCoords(1)
                 If Err.Number=0 Then placeX=CDbl(tX): placeY=CDbl(tY): bGotCoords=True Else totalErrorsEncountered=totalErrorsEncountered+1: Err.Clear
                 On Error GoTo 0
            End If
            Dim oDimValueObject: On Error Resume Next
            Set oDimValueObject = objToNumber.GetValue()
            If Not oDimValueObject Is Nothing Then
                 Dim cBT, tempN, xPos, numPart
                 oDimValueObject.GetBaultText 1, cBT, "", "", ""
                 If Len(Trim(cBT)) > 0 Then
                      xPos = InStr(UCase(Trim(cBT)), "X"): If xPos > 1 Then numPart = Trim(Left(Trim(cBT), xPos-1))
                      If IsNumeric(numPart) Then tempN = CLng(numPart): If tempN > 1 Then N = tempN
                 End If
            End If: On Error GoTo 0
        ElseIf itemType = "DrawingGDT" Then
             On Error Resume Next: placeX = objToNumber.x: placeY = objToNumber.y
             If Err.Number = 0 Then bGotCoords = True Else totalErrorsEncountered=totalErrorsEncountered+1: Err.Clear
             On Error GoTo 0
        End If

        ' Calculate & Format Output
        Dim outputTextContent, nStart, nEnd, sVVNN, eVVNN
        nStart=currentSequenceNN: nEnd=currentSequenceNN+N-1: sVVNN=FormatSeqNumber(sViewIndexPadded,nStart)
        Select Case N
            Case 1: outputTextContent = sVVNN
            Case 2: eVVNN=FormatSeqNumber(sViewIndexPadded,nEnd): outputTextContent = sVVNN & "," & eVVNN
            Case Else: eVVNN=FormatSeqNumber(sViewIndexPadded,nEnd): outputTextContent = sVVNN & ",..," & eVVNN
        End Select

        ' Create Text
        Dim oNewText, textFinalY, bTextCreated
        Set oNewText = Nothing: textFinalY = placeY + TEXT_VERTICAL_OFFSET: bTextCreated = False
        On Error Resume Next
        Set oNewText = oTexts.Add(outputTextContent, placeX, textFinalY)
        If Err.Number=0 And Not oNewText Is Nothing Then bTextCreated = True Else totalErrorsEncountered=totalErrorsEncountered+1: Err.Clear
        On Error GoTo 0

        ' Set Associativity
        If bTextCreated Then
            On Error Resume Next
            oNewText.AssociativeElement = objToNumber
            If Err.Number = 0 Then totalAssocSetSuccess = totalAssocSetSuccess + 1 Else totalErrorsEncountered=totalErrorsEncountered+1: Err.Clear
            On Error GoTo 0
        End If

        currentSequenceNN = currentSequenceNN + N
    Next

    MsgBox "--- Dim & GDT Numbering Finished ---" & vbCrLf & "Items processed: " & totalItemsProcessed, vbInformation
End Sub

Private Function FormatSeqNumber(viewPrefixVV, sequenceNN)
    FormatSeqNumber = viewPrefixVV & Right("0" & CStr(sequenceNN), 2)
End Function
